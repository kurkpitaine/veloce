DENM-PDU-Descriptions {itu-t (0) identified-organization (4) etsi (0) itsDomain (5) wg1 (1) denmPduRelease2 (103831) major-version-2 (2) minor-version-1 (1)}

DEFINITIONS AUTOMATIC TAGS ::=

BEGIN

IMPORTS

ActionId, ActionIdList, CauseCodeV2, ClosedLanes, DangerousGoodsExtended, DeltaReferencePosition, DeltaTimeMilliSecondPositive, DeltaTimeSecond,
EnergyStorageType, EventZone, HeightLonCarr, InformationQuality, ItsPduHeader, LanePosition, LightBarSirenInUse, ItineraryPath, NumberOfOccupants,
PosLonCarr, PosCentMass, PositionOfPillars, PositioningSolutionType, PosFrontAx, PositionOfOccupants, RequestResponseIndication, ReferencePosition,
RestrictedTypes, RoadType, StandardLength3b, StationType, Speed, SpeedLimit, StationarySince, TimestampIts, Traces,
TrafficDirection, TrafficRule, TurningRadius, Temperature, VehicleMass, VehicleIdentification, Wgs84Angle, WheelBaseVehicle

FROM ETSI-ITS-CDD {itu-t (0) identified-organization (4) etsi (0) itsDomain (5) wg1 (1) ts (102894) cdd (2) major-version-3 (3) minor-version-1 (1)}
;


DENM ::= SEQUENCE {
	header ItsPduHeader (WITH COMPONENTS {... , protocolVersion (2), messageId(denm)}),
	denm   DenmPayload
}

DenmPayload ::= SEQUENCE {
	management ManagementContainer,
	situation  SituationContainer OPTIONAL,
	location   LocationContainer OPTIONAL,
	alacarte   AlacarteContainer OPTIONAL
}

ManagementContainer ::= SEQUENCE {
	actionId                  ActionId,
	detectionTime             TimestampIts,
	referenceTime             TimestampIts,
	termination               Termination OPTIONAL,
	eventPosition             ReferencePosition,
	awarenessDistance         StandardLength3b OPTIONAL,
	awarenessTrafficDirection TrafficDirection OPTIONAL,
	validityDuration          DeltaTimeSecond DEFAULT defaultValidity,
	transmissionInterval      DeltaTimeMilliSecondPositive OPTIONAL,
	stationType               StationType,
	...
}

SituationContainer ::= SEQUENCE {
	informationQuality InformationQuality,
	eventType          CauseCodeV2,
	linkedCause        CauseCodeV2 OPTIONAL,
	eventZone          EventZone OPTIONAL,
	...
}

LocationContainer ::= SEQUENCE {
	eventSpeed           Speed OPTIONAL,
	eventPositionHeading Wgs84Angle OPTIONAL,
	traces               Traces,
	roadType             RoadType OPTIONAL,
	...
}

ImpactReductionContainer ::= SEQUENCE {
	heightLonCarrLeft         HeightLonCarr,
	heightLonCarrRight        HeightLonCarr,
	posLonCarrLeft            PosLonCarr,
	posLonCarrRight           PosLonCarr,
	positionOfPillars         PositionOfPillars,
	posCentMass               PosCentMass,
	wheelBaseVehicle          WheelBaseVehicle,
	turningRadius             TurningRadius,
	posFrontAx                PosFrontAx,
	positionOfOccupants       PositionOfOccupants,
	vehicleMass               VehicleMass,
	requestResponseIndication RequestResponseIndication
}

RoadWorksContainerExtended ::= SEQUENCE {
	lightBarSirenInUse      LightBarSirenInUse OPTIONAL,
	closedLanes             ClosedLanes OPTIONAL,
	restriction             RestrictedTypes OPTIONAL,
	speedLimit              SpeedLimit OPTIONAL,
	incidentIndication      CauseCodeV2 OPTIONAL,
	recommendedPath         ItineraryPath OPTIONAL,
	startingPointSpeedLimit DeltaReferencePosition OPTIONAL,
	trafficFlowRule         TrafficRule OPTIONAL,
	referenceDenms          ActionIdList OPTIONAL
 }

StationaryVehicleContainer ::= SEQUENCE {
	stationarySince        StationarySince OPTIONAL,
	stationaryCause        CauseCodeV2 OPTIONAL,
	carryingDangerousGoods DangerousGoodsExtended OPTIONAL,
	numberOfOccupants      NumberOfOccupants OPTIONAL,
	vehicleIdentification  VehicleIdentification OPTIONAL,
	energyStorageType      EnergyStorageType OPTIONAL
}

AlacarteContainer ::= SEQUENCE {
	lanePosition        LanePosition OPTIONAL,
	impactReduction     ImpactReductionContainer OPTIONAL,
	externalTemperature Temperature OPTIONAL,
	roadWorks           RoadWorksContainerExtended OPTIONAL,
	positioningSolution PositioningSolutionType OPTIONAL,
	stationaryVehicle   StationaryVehicleContainer OPTIONAL,
	...
}

defaultValidity INTEGER ::= 600

Termination ::= ENUMERATED {isCancellation(0), isNegation (1)}

END
